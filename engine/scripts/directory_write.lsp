;; Directory-only writer. Never loads replace_frames.lsp; never inserts or explodes.
;; SCR and this adapter are ASCII. Payload uses Unicode chr only after LISPSYS check.
(defun dcw:path (name) (strcat (getvar "DWGPREFIX") name))
(defun dcw:require (ok message) (if (not ok) (error message)))
(defun dcw:load-patches ()
 (dcw:require (and (>= (atoi (getvar "ACADVER")) 24) (> (getvar "LISPSYS") 0))
  "Unicode AutoLISP is required. Set LISPSYS=1 and restart CAD before retrying.")
 (load (dcw:path "patches.lsp")))
(defun dcw:canon (v)
 (cond ((null v) "nil")
  ((= (type v) 'ENAME) (strcat "@" (cdr (assoc 5 (entget v)))))
  ((= (type v) 'REAL) (strcat "R" (rtos v 2 16)))
  ((= (type v) 'INT) (strcat "I" (itoa v)))
  ((= (type v) 'STR) (strcat "S" (vl-prin1-to-string v)))
  ((listp v) (strcat "(" (dcw:canon (car v)) "." (dcw:canon (cdr v)) ")"))
  (T (vl-prin1-to-string v))))
(defun dcw:protected (e / d handle target out pair)
 (setq d (entget e '("*")) handle (cdr (assoc 5 d)) target (assoc handle dcw:patches) out nil)
 (foreach pair d
  (if (and (/= (car pair) -1) (not (and target (member (car pair) '(1 3)))))
   (setq out (cons pair out))))
 (strcat handle "\t" (dcw:canon (reverse out))))
(defun dcw:dict-entities (dictionary / entry out object)
 (setq out (list dictionary) entry (dictnext dictionary T))
 ;; Do not recurse using dictnext: recursion shares its iterator. Collect first.
 (while entry
  (setq object (cdr (assoc 350 entry)))
  (if (not object) (setq object (cdr (assoc 360 entry))))
  (if object (setq out (cons object out)))
  (setq entry (dictnext dictionary))) out)
(defun dcw:audit (name / entities e row b table record group f line)
 (setq entities nil e (entnext))
 (while e (setq entities (cons e entities) e (entnext e)))
 ;; Block definitions and table records cover frame geometry, styles and xref settings.
 (foreach table '("BLOCK" "LAYER" "LTYPE" "STYLE" "DIMSTYLE" "UCS" "VPORT" "VIEW" "APPID")
  (setq row (tblnext table T))
  (while row
   (setq record (tblobjname table (cdr (assoc 2 row))))
   (if record (setq entities (cons record entities)))
   (if (= table "BLOCK")
    (progn
     (setq b (cdr (assoc -2 row)))
     (while b
      (setq entities (cons b entities))
      (if (= (cdr (assoc 0 (entget b))) "ENDBLK") (setq b nil) (setq b (entnext b))))))
   (setq row (tblnext table))))
 ;; GROUP membership lives outside the graphical entity stream.
 (setq group (dictsearch (namedobjdict) "ACAD_GROUP"))
 (if group (setq entities (append entities (dcw:dict-entities (cdr (assoc -1 group))))))
 (setq entities (vl-sort entities (function (lambda (a b) (< (cdr (assoc 5 (entget a))) (cdr (assoc 5 (entget b))))))))
 (setq f (open (dcw:path name) "w" "utf8"))
 (dcw:require f "Cannot create audit evidence.")
 (write-line "CAD100_PROTECTED_V1" f)
 (foreach e entities (write-line (dcw:protected e) f))
 (write-line "DONE" f) (close f))
(defun dcw:contents (data / ordinary embedded inside pair)
 (setq ordinary "" embedded "" inside nil)
 (foreach pair data
  (cond ((and (= (car pair) 101) (= (cdr pair) "Embedded Object")) (setq inside T))
   ((member (car pair) '(1 3))
    (if inside (setq embedded (strcat embedded (cdr pair))) (setq ordinary (strcat ordinary (cdr pair)))))))
 (list ordinary embedded inside))
(defun dcw:validate (p / e d content parent layer)
 (setq e (handent (nth 0 p)) d (if e (entget e)) content (dcw:contents d))
 (dcw:require (and d (= (cdr (assoc 0 d)) "ATTRIB") (= (cdr (assoc 2 d)) (nth 2 p))) "Attribute identity changed.")
 (setq parent (cdr (assoc 330 d)))
 (dcw:require (and parent (= (cdr (assoc 5 (entget parent))) (nth 1 p))) "Attribute owner changed.")
 (dcw:require (and (= (car content) (nth 3 p)) (= (cadr content) (nth 4 p)) (equal (caddr content) (nth 5 p))) "Original attribute content changed.")
 (dcw:require (= (logand (if (assoc 70 d) (cdr (assoc 70 d)) 0) 1) 0) "Invisible attribute is not writable in this trial.")
 (setq layer (tblsearch "LAYER" (cdr (assoc 8 d))))
 (dcw:require (= (logand (cdr (assoc 70 layer)) 4) 0) "Attribute layer is locked.")
 (dcw:require (assoc 1 d) "Attribute has no text payload.")
 e)
(defun dcw:patch (p / e d inside out pair text-seen embedded-seen)
 (setq e (dcw:validate p) d (entget e) inside nil out nil text-seen nil embedded-seen nil)
 (foreach pair d
  (cond
   ((and (= (car pair) 101) (= (cdr pair) "Embedded Object")) (setq inside T out (cons pair out)))
   ((member (car pair) '(1 3))
    (if inside
     (if (not embedded-seen) (setq out (cons (cons 1 (nth 7 p)) out) embedded-seen T))
     (if (not text-seen) (setq out (cons (cons 1 (nth 6 p)) out) text-seen T))))
   (T (setq out (cons pair out)))))
 (dcw:require (or (not (nth 5 p)) embedded-seen) "Missing embedded payload.")
 (dcw:require (entmod (reverse out)) "CAD rejected attribute update.")
 (entupd e)
 (dcw:require (equal (dcw:contents (entget e)) (list (nth 6 p) (nth 7 p) (nth 5 p))) "CAD did not retain requested text."))
(defun dcw:dependencies (/ row flags key)
 ;; Do not publish a moved copy whose relative external references may no longer resolve.
 (setq row (tblnext "BLOCK" T))
 (while row
  (setq flags (cdr (assoc 70 row)))
  (dcw:require (= (logand (if flags flags 0) 12) 0) "External dependencies require manual packaging.")
  (setq row (tblnext "BLOCK")))
 (foreach key '("ACAD_IMAGE_DICT" "ACAD_PDFDEFINITIONS" "ACAD_DWFDEFINITIONS" "ACAD_DGNDEFINITIONS")
  (dcw:require (not (dictsearch (namedobjdict) key)) "External dependencies require manual packaging.")))
(defun dcw:apply (/ p f)
 (dcw:load-patches)
 (dcw:dependencies)
 (dcw:require dcw:patches "No approved changes.")
 (foreach p dcw:patches (dcw:validate p))
 (dcw:audit "before.txt")
 (foreach p dcw:patches (dcw:patch p))
 (dcw:audit "after.txt")
 (command "_.QSAVE")
 (dcw:require (= (getvar "DBMOD") 0) "Save did not finish.")
 (setq f (open (dcw:path "written.ok") "w")) (write-line "SAVED" f) (close f))
(defun dcw:failure (result / f)
 (setq f (open (dcw:path "native_error.txt") "w" "utf8"))
 (if f (progn (write-line (vl-catch-all-error-message result) f) (close f)))
 (princ (strcat "\nDIRECTORY FAILED: " (vl-catch-all-error-message result))))
(defun dcw:run (/ result)
 (setq result (vl-catch-all-apply 'dcw:apply nil))
 (if (vl-catch-all-error-p result) (dcw:failure result))
 (princ))
(defun dcw:verify-work ()
 (dcw:load-patches) (dcw:audit "reopened.txt")
 (setq dcs:output (dcw:path "entities.tsv")) (c:CAD100DIRECTORYSCAN))
(defun dcw:verify (/ result)
 (setq result (vl-catch-all-apply 'dcw:verify-work nil))
 (if (vl-catch-all-error-p result) (dcw:failure result))
 (princ))
(princ)
