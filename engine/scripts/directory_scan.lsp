;; Trial read adapter. No ActiveX getters, entmod, entdel, setvar or DWG save.
(defun dcs:s (v)
 (cond ((null v) "") ((= (type v) 'REAL) (rtos v 2 16))
 ((= (type v) 'INT) (itoa v)) ((= (type v) 'STR) v)
 ((listp v) (strcat "(" (dcs:s (car v)) " " (dcs:s (cadr v)) " " (dcs:s (caddr v)) ")"))
 (T (vl-princ-to-string v))))
(defun dcs:escape (v / s c out)
 (setq out "")
 (foreach c (vl-string->list (dcs:s v))
  (setq out (strcat out (cond ((= c 92) "\\\\") ((= c 9) "\\t")
   ((= c 10) "\\n") ((= c 13) "\\r") (T (chr c)))))) out)
(defun dcs:line (values / out first)
 (setq out "" first T)
 (foreach v values (setq out (strcat out (if first "" "\t") (dcs:escape v)) first nil))
 (write-line out dcs:file))
(defun dcs:entity (e parent / d plain embedded flag raw pair)
 (setq d (entget e) plain "" embedded "" flag nil raw "")
 (foreach pair d
  (setq raw (strcat raw (itoa (car pair)) "=" (dcs:s (cdr pair)) "\n"))
  (cond ((and (= (car pair) 101) (= (cdr pair) "Embedded Object")) (setq flag T))
   ((member (car pair) '(1 3))
    (if flag (setq embedded (strcat embedded (cdr pair))) (setq plain (strcat plain (cdr pair)))))))
 (dcs:line (list "ENTITY" (cdr (assoc 0 d)) (cdr (assoc 5 d)) parent
  (cdr (assoc 410 d)) (cdr (assoc 8 d)) (cdr (assoc 2 d)) plain (if flag "1" "0") embedded
  (cdr (assoc 10 d)) (cdr (assoc 11 d)) (cdr (assoc 40 d))
  (cdr (assoc 41 d)) (cdr (assoc 42 d)) (cdr (assoc 43 d)) (cdr (assoc 50 d)) raw)))
(defun dcs:edges (d / ps p prev first flags)
 (setq ps nil)
 (foreach p d (if (= (car p) 10) (setq ps (append ps (list (cdr p))))))
 (setq first (car ps) prev first)
 (foreach p (cdr ps)
  (dcs:line (list "ENTITY" "LINE" (cdr (assoc 5 d)) "" (cdr (assoc 410 d)) (cdr (assoc 8 d)) "" "" "0" "" prev p))
  (setq prev p))
 (setq flags (cdr (assoc 70 d)))
 (if (not (numberp flags)) (setq flags 0))
 (if (and first prev (= (logand flags 1) 1))
  (dcs:line (list "ENTITY" "LINE" (cdr (assoc 5 d)) "" (cdr (assoc 410 d)) (cdr (assoc 8 d)) "" "" "0" "" prev first))))
(defun c:CAD100DIRECTORYSCAN (/ *error* ss i e d child cd start opened encoding)
 (defun *error* (m)
  (if dcs:file (progn (dcs:line (list "ERROR" m)) (close dcs:file) (setq dcs:file nil)))
  (princ (strcat "\nDirectory audit failed: " m)) (princ))
 (setq start (getvar "DBMOD"))
 (setq opened (vl-catch-all-apply 'open (list dcs:output "w" "utf8")))
 (if (vl-catch-all-error-p opened)
  (setq dcs:file (open dcs:output "w") encoding "SYSTEM")
  (setq dcs:file opened encoding "UTF8"))
 (if dcs:file
  (progn
   (dcs:line (list "META" "CAD100_DIRECTORY_SCAN_V1" (getvar "ACADVER") start encoding))
   (setq ss (ssget "_X") i 0)
   (if ss (repeat (sslength ss)
    (setq e (ssname ss i) d (entget e) i (1+ i))
    (if (member (cdr (assoc 0 d)) '("TEXT" "MTEXT" "INSERT" "LINE" "ACAD_TABLE"))
     (progn
      (dcs:entity e "")
      (if (and (= (cdr (assoc 0 d)) "INSERT") (= (cdr (assoc 66 d)) 1))
       (progn
        (setq child (entnext e))
        (while child
         (setq cd (entget child))
         (if (= (cdr (assoc 0 cd)) "ATTRIB")
          (progn (dcs:entity child (cdr (assoc 5 d))) (setq child (entnext child)))
          (setq child nil)))))))
    (if (= (cdr (assoc 0 d)) "LWPOLYLINE") (dcs:edges d))))
   (dcs:line (list "DONE" start (getvar "DBMOD")))
   (close dcs:file) (setq dcs:file nil)))
 (princ))
(princ)
